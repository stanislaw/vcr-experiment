[DOCUMENT]
TITLE: Vehicle Network Gateway Devices Security Requirements

[GRAMMAR]
ELEMENTS:
- TAG: REQUIREMENT
  FIELDS:
  - TITLE: UID
    TYPE: String
    REQUIRED: True
  - TITLE: LEVEL
    TYPE: String
    REQUIRED: False
  - TITLE: STATUS
    TYPE: String
    REQUIRED: False
  - TITLE: TAGS
    TYPE: String
    REQUIRED: False
  - TITLE: REFS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  - TITLE: PUB_REFS
    TYPE: String
    REQUIRED: False
  - TITLE: VERIFICATION
    TYPE: String
    REQUIRED: False
  - TITLE: CRITICALITY
    TYPE: String
    REQUIRED: False

[FREETEXT]
This document captures security requirements for vehicle network gateway devices: both devices intended to be gateways and those devices which *could be a gateway* (due to malicious code).

Intended Gateway:
    A device which had connections to multiple vehicle network domains (or segments) and is intended to transport, translate, filter/drop/rate-limit or encapsulate information from an Untrusted Network Domain (*UND*) to a Trusted Network Domain (*TND*). Any device which performs one or more of these functions is an intended gateway. See the section *Abstract (Intended) Gateway Core Functional Requirements* for more details.

Unintended Gateway:
    A device which could be a gateway (due to malicious code) but is not intended to be one. See the section *Prevents Gateway Functions* for details on the security assurance necessary to prevent gateway functionality on unintended gateways.

Intended gateways are designed to transport, translate etc. between two separate network domains (or segments). They do so asymmetrically, treating one segment as trustworthy.

Untrusted Network Domain (*UND*):
    A *UND* is a network domain (or segment) that contains **any** of the following:

    a) wireless communication or reachable wirelessly (e.g J2497)
    b) an interface for aftermarket devices or operator access (e.g. an OBD port)
    c) a telematics device that does not satisfy the HD VCR requirements
    d) a multi-network device (e.g. intended or unintended gateway) that does not satisfy the HD VCR requirements

Trusted Network Domain (*TND*):
    A *TND* is a network domain (or segment) that **does not contain any** of the following:

    a) wireless communication or reachable wirelessly (e.g J2497)
    b) an interface for aftermarket devices or operator access (e.g. an OBD port)
    c) a telematics device that does not satisfy the HD VCR requirements
    d) a multi-network device (e.g. intended or unintended gateway) that does not satisfy the HD VCR requirements

Some Examples:

The RP1226 connector is made for connecting aftermarket devices; therefore the databuses there are UNDs.
::


            ┌───────────────┐                 ┌──────────────┐                     ┌─┐
            │  Gateway sat  │                 │              │                     │┼│
    ────────┤   all HDVCR   ├─────────────────┤    RP1226    ├─────────────────────┼┼│
      TND   │  requirements │     UND         │   Connector  │      UND            │┼│
            └───────────────┘                 └──────────────┘                     └─┘


The OBD connector is _the_ operator access port; therefore the databuses there are UNDs.
::


            ┌───────────────┐                 ┌──────────────┐                     ┌─┐
            │  Gateway sat  │                 │              │                     │┼│
    ────────┤   all HDVCR   ├─────────────────┤      OBD     ├─────────────────────┼┼│
      TND   │  requirements │     UND         │   Connector  │      UND            │┼│
            └───────────────┘                 └──────────────┘                     └─┘



Note on options for requirements: This document contains requirements where the working group cannot reasonably require a particular implementation option, only that one of the satisfactory ways to satisfy the requirement is implemented. Modelling these 'options' requirements is not possible nor reccomended: the sheer number of requirements which will be captured for heavy vehicles means that the requirements must remain machine readable and there is no machine readable way to communicate options to implementors (for good reason). The approach that is taken is to a) include the options as notes to the implementers of these requirements and b) to tag all requirements with `CONTAINS_OPTIONS` so the entire list of requirements containing notes to the implementers can be indexed for easy reference by them.
[/FREETEXT]

[SECTION]
TITLE: Security Requirements for Abstract (Intended) Gateways

[FREETEXT]
The following requirements must be satisfied by any device intended to be a gateway on *any type of* vehicle networks. There are CAN-specific and J1939-sepcific requirements in the CGW- and J1939GW- series below.
[/FREETEXT]

[REQUIREMENT]
UID: AGW-S-000
TITLE: Gateway Configuration Protected
STATEMENT: The device SHALL accept and react only to configuration changes which are correctly authorized and authenticated, regardless of origin of network domain.
PUB_REFS: >>>
TODO
<<<
CRITICALITY: High

[REQUIREMENT]
UID: AGW-S-001
TITLE: Prevents OTA
STATEMENT: The device SHALL prevent Over The Air updates (OTA) (including parameter flash) from *UND* to *TND*, unless with explicitly authorized and authenticated configuration changes via the mode switch.
PUB_REFS: >>>
TODO
<<<
CRITICALITY: High

[REQUIREMENT]
UID: AGW-S-002
TITLE: Prevents DoS
STATEMENT: The device SHALL prevent generating Denial of Service (DoS) on *TND* from messages originating on *UND*.
PUB_REFS: >>>

    It is recommended to isolate safety-critical ECUs on their own CAN bus, with some sort of gateway between them and other ECUs

    -- FMCSA GDL 37

<<<
CRITICALITY: High

[REQUIREMENT]
UID: AGW-S-003
TITLE: Prevents Spoofing
STATEMENT: The device SHALL prevent spoofing/masquerading/injection onto *TND*
PUB_REFS: >>>

    It is recommended to isolate safety-critical ECUs on their own CAN bus, with some sort of gateway between them and other ECUs

    -- FMCSA GDL 37

<<<
CRITICALITY: High

[REQUIREMENT]
UID: AGW-S-004
TAGS: CONTAINS_OPTIONS
TITLE: Prevents Exfiltration
STATEMENT: >>>
The device SHALL prevent exfiltration of data from *TND* to *UND*, or vice-versa, by satisfying one or more of these methods:

* Protect Confidentiality: These devices MAY encapsulate and/or translate (e.g. encrypt) information as it is transported between the network domains for the purposes of protecting confidentiality of the information in the domain to which the information is moved.
* Re-Write / Masking: The device SHALL provide a means of masking or otherwise re-writing data to prevent exfiltration of sensitive information from *TND* to *UND*.

<<<
PUB_REFS: >>>
TODO
<<<
CRITICALITY: High

[REQUIREMENT]
UID: AGW-S-005
TITLE: Prevents Elevation
STATEMENT: The device SHALL prevent abuse of *TND* network domain functionality from *UND* to *TND*, unless with explicitly authorized and authenticated configuration changes via the mode switch.
PUB_REFS: >>>

    It is recommended to isolate safety-critical ECUs on their own CAN bus, with some sort of gateway between them and other ECUs

    -- FMCSA GDL 37

<<<
CRITICALITY: High

[REQUIREMENT]
UID: AGW-S-006
TITLE: Prevents Data Loss
STATEMENT: The device SHALL prevent all data loss and/or corruption of information in the bidirectional *UND* ↔ *TND* operation, unless with explicit configuration for rate limiting (AGW-F-006) or translation (AGW-F-002).
PUB_REFS: >>>
TODO
<<<
CRITICALITY: High

[REQUIREMENT]
UID: AGW-S-007
TITLE: Preserves High Side Operation
STATEMENT: The device SHALL prevent degradation of any *TND* operation due to *UND* activity.
PUB_REFS: >>>
TODO
<<<
CRITICALITY: High

[REQUIREMENT]
UID: AGW-S-008
TITLE: Security Assurance
STATEMENT: These devices SHALL satisfy a comprehensive set of product security requirements to yield high assurance of correct operation in the face of adversarial inputs to the device.
PUB_REFS: >>>
TODO
<<<
CRITICALITY: High

[REQUIREMENT]
UID: AGW-S-009
REFS:
- TYPE: Parent
  VALUE: AGW-S-007
TITLE: Preserves Performance
STATEMENT: The device SHALL be scoped to sufficient detail to preserve network domain performance guarantees in *TND*.
PUB_REFS: >>>
TODO
<<<
CRITICALITY: Medium

[REQUIREMENT]
UID: AGW-S-010
TAGS: CONTAINS_OPTIONS
TITLE: Mode Switch Interlock
STATEMENT: >>>
The device SHALL have a means to temporarily disable the preventions listed previously and as noted with "unless with explicity authorized and authenticated configuration changes via the mode switch" The means must be impossible to use without explicit authorization by the vehicle owner. The device SHALL satisfy one or more of these methods to enable a switch into modes which allow OTA, spoofing, etc. from *UND* to *TND*. If more than one is satisfied then the effects of either switch could be in effect concurrently (i.e. a logical OR operation).

* Physical Mode Switch Interlock: The device SHALL have at least one physical input that when grounded enables a switch into modes which allow OTA, spoofing, etc. from *UND* to *TND*.

  * Example: Physical switch on dash

* Virtual Mode Switch Interlock: The device SHALL allow a explicitly authorized and authenticated input over a connection to enable a switch into modes which allow OTA, spoofing, etc. from *UND* to *TND*.

  * Example: Consent on Instrument cluster or infotainment device (and thus internal networks - possibly but not necessarily *TND*)

  * Example: Consent from third party device / application that is signed with infrastructure OEM has access to verify

<<<
PUB_REFS: >>>
TODO
<<<
CRITICALITY: High

[REQUIREMENT]
UID: AGW-S-011
TITLE: Mode Switch Indicated
STATEMENT: The device SHALL indicate to all domains that it is not performing normal operations.
PUB_REFS: >>>
TODO
<<<
CRITICALITY: Medium

[SECTION]
TITLE: Security Requirements for CAN Gateways

[FREETEXT]
The following security requirements must be satisfied by CAN gateways specifically. These CAN gateways are expected to meet all of the AGW-S-* Abstract Gateway security requirements and to also satisfy the CGW-S-* security requirements of this section.
[/FREETEXT]

[REQUIREMENT]
UID: CGW-S-001
REFS:
- TYPE: Parent
  VALUE: AGW-S-009
TITLE: Performant
STATEMENT: The device SHALL process and move CAN frames quickly enough to preserve performance on all network domains.
PUB_REFS: >>>
TODO
<<<
CRITICALITY: Medium

[SECTION]
TITLE: Preserves Atomic Multicast: CGW-S-005* Series

[FREETEXT]
The device SHALL preserve the atomic multicast property of CAN buses. All CGW-S-005* requirements must be satisfied.
[/FREETEXT]

[REQUIREMENT]
UID: CGW-S-005a
REFS:
- TYPE: Parent
  VALUE: AGW-S-007
TITLE: Won't Drop Frames
STATEMENT: The device SHALL NOT drop CAN frames in its bidirectional *UND* ↔ *TND* operation, unless with explicit configuration for rate limiting or translating.
PUB_REFS: >>>
TODO
<<<
CRITICALITY: High

[REQUIREMENT]
UID: CGW-S-005b
REFS:
- TYPE: Parent
  VALUE: AGW-S-007
TITLE: No Priority Inversion
STATEMENT: The device SHALL schedule egress frames according to the CAN arbitration ID priority in it bidirectional *UND* ↔ *TND* operation, to prevent priority inversion.
PUB_REFS: >>>
TODO
<<<
CRITICALITY: High

[REQUIREMENT]
UID: CGW-S-005c
REFS:
- TYPE: Parent
  VALUE: AGW-S-007
TITLE: Preserves Ordering
STATEMENT: The device SHALL preserve ordering egress frames with respect to their ingress order within an equivalence class of CAN arbitration ID priorities, to prevent out-of-order delivery.
PUB_REFS: >>>
TODO
<<<
CRITICALITY: High

[REQUIREMENT]
UID: CGW-S-005d
REFS:
- TYPE: Parent
  VALUE: AGW-S-007
TITLE: FIFO but Also Priority
STATEMENT: The device SHALL schedule egress for in-order send but not across CAN arbitration ID priorities.
PUB_REFS: >>>
TODO
<<<
CRITICALITY: High

[REQUIREMENT]
UID: CGW-S-005e
REFS:
- TYPE: Parent
  VALUE: AGW-S-007
TITLE: Preserves Jitter
STATEMENT: The device SHALL have ingress-to-egress latency variability (jitter) low enough to not affect the *TND* network domain performance requirements in the worst case.
PUB_REFS: >>>
TODO
<<<
CRITICALITY: Medium

[/SECTION]

[SECTION]
TITLE: Prevents CAN Attacks

[REQUIREMENT]
UID: CGW-S-006
REFS:
- TYPE: Parent
  VALUE: AGW-S-002
TITLE: Prevents Bus Flood Attacks
STATEMENT: The device SHALL prevent generating bus flood attacks on *TND* from messages originating on *UND*.
PUB_REFS: >>>
https://canislabs.com/wp-content/uploads/2020/05/1901-2019-11-29-White-Paper-CAN-Security.pdf section 2.1 for a description of the bus flood attack.
<<<
CRITICALITY: High

[REQUIREMENT]
UID: CGW-S-007
REFS:
- TYPE: Parent
  VALUE: AGW-S-003
TITLE: Prevents (Simple) Frame Spoofing
STATEMENT: The device SHALL prevent generating simple frame spoofing attacks on *TND* from messages originating on *UND*.
PUB_REFS: >>>
https://canislabs.com/wp-content/uploads/2020/05/1901-2019-11-29-White-Paper-CAN-Security.pdf section 2.2 for a description of simple frame spoofing attack.
<<<
CRITICALITY: High

[SECTION]
TITLE: Prevents CAN Protocol Attacks: CGW-S-008* Series

[FREETEXT]
The CAN gateways must prevent CAN protocol attacks in *TND*. At the time of drafting these requirements this can be accomplished by satisfying all of the CGW-S-008* requirements that follow.

CAN Protocol Attack
    Attacks on CAN networks requiring GPIO control of CAN_TX (and optionally CAN_RX) pins.

c.f. https://canislabs.com/wp-content/uploads/2020/05/1901-2019-11-29-White-Paper-CAN-Security.pdf section 2.1 for further definition of CAN protocol attacks.
[/FREETEXT]

[REQUIREMENT]
UID: CGW-S-008a
REFS:
- TYPE: Parent
  VALUE: AGW-S-003
TITLE: Prevents Adaptive Frame Spoofing
STATEMENT: The device SHALL prevent generating adaptive frame spoofing attacks on *TND* from messages originating on *UND*.
PUB_REFS: >>>
https://canislabs.com/wp-content/uploads/2020/05/1901-2019-11-29-White-Paper-CAN-Security.pdf section 2.3 for a description of adaptive frame spoofing attack.
<<<
CRITICALITY: High

[REQUIREMENT]
UID: CGW-S-008b
REFS:
- TYPE: Parent
  VALUE: AGW-S-007
TITLE: Prevents Error Passive Attack Step
STATEMENT: The device SHALL prevent generating attacks that drive a ECU on *TND* into error passive state from messages originating on *UND*. This will in turn prevent error passive spoofing attacks.
PUB_REFS: >>>
https://canislabs.com/wp-content/uploads/2020/05/1901-2019-11-29-White-Paper-CAN-Security.pdf section 2.4 for a description of error passive spoofing attack.
<<<
CRITICALITY: High

[REQUIREMENT]
UID: CGW-S-008c
REFS:
- TYPE: Parent
  VALUE: AGW-S-007
TITLE: Prevents Double Receive Attack
STATEMENT: The device SHALL prevent generating double receive attacks on *TND* from messages originating on *UND*.
PUB_REFS: >>>
https://canislabs.com/wp-content/uploads/2020/05/1901-2019-11-29-White-Paper-CAN-Security.pdf section 2.5 for a description of the double receive attack.
<<<
CRITICALITY: High

[REQUIREMENT]
UID: CGW-S-008d
REFS:
- TYPE: Parent
  VALUE: AGW-S-002
TITLE: Prevents Bus-Off Attack
STATEMENT: The device SHALL prevent generating bus-off attacks on *TND* from messages originating on *UND*.
PUB_REFS: >>>
https://canislabs.com/wp-content/uploads/2020/05/1901-2019-11-29-White-Paper-CAN-Security.pdf section 2.6 for a description of the bus-off attack.
<<<
CRITICALITY: High

[REQUIREMENT]
UID: CGW-S-008e
REFS:
- TYPE: Parent
  VALUE: AGW-S-002
TITLE: Prevents Freeze Doom Loop Attack
STATEMENT: The device SHALL prevent generating freeze doom loop attacks on *TND* from messages originating on *UND*.
PUB_REFS: >>>
https://canislabs.com/wp-content/uploads/2020/05/1901-2019-11-29-White-Paper-CAN-Security.pdf section 2.7 for a description of the freeze doom loop attack.
<<<
CRITICALITY: High

[/SECTION]

[REQUIREMENT]
UID: CGW-S-013
REFS:
- TYPE: Parent
  VALUE: AGW-S-008
TITLE: Impervious to Janus Attack
STATEMENT: The device SHALL not enable Janus Attacks in any group of OEM supplied components on any of its interface.
COMMENT: Susceptibility to Janus Attacks is a property of a network of devices, not only of a single device. The entire *TND* is expected to be impervious to Janus Attacks since it should all be OEM supplied components there. In *UND* it is not possible to require that this device nor all the devices are impervious to Janus Attacks since *UND* is explicitly permitted to contain non-OEM supplied components. What is required of this device on *UND* is that if there are other OEM supplied devices on *UND* then this device cannot enable Janus Attacks on that collection of all those OEM supplied devices on *UND*.
PUB_REFS: >>>
https://kentindell.github.io/2021/07/15/janus-attack/ for a description of the Janus Attack
<<<
CRITICALITY: Medium

[/SECTION]

[/SECTION]

[SECTION]
TITLE: Security Requirements for J1939 Gateways

[FREETEXT]
J1939 Gateways are expected to meet all of the CGW-S-* CAN Gateway Security Requirements and to also satisfy the J1939GW-S-* Security requirements of this section
[/FREETEXT]

[REQUIREMENT]
UID: J1939GW-S-039
REFS:
- TYPE: Parent
  VALUE: AGW-S-003
TITLE: Prevents J1939 Address Spoofing
STATEMENT: The device shall prevent the gatewaying (any of transport, translate, filter, or encapsulate) of any traffic onto *TND* with a J1939 address which is claimed by any of the devices in *TND*.
PUB_REFS: >>>
TODO
<<<
CRITICALITY: Medium

[REQUIREMENT]
UID: J1939GW-S-029
REFS:
- TYPE: Parent
  VALUE: AGW-S-002
TITLE: Prevents Address Claim Attacks
STATEMENT: The device SHALL prevent generating address claim attacks on *TND* from messages originating on *UND*.
COMMENT: **Note to implementors**: Performing no gatewaying (any of transport, translate, filter, or encapsulate) of address claims onto *TND* would satisfy this requirement.
PUB_REFS: >>>
https://www.aut.upt.ro/~bgroza/Papers/j1939.pdf and https://doi.org/10.4271/02-14-03-0026 for a description of the address claim attack.

TODO
<<<
CRITICALITY: High

[REQUIREMENT]
UID: J1939GW-S-089
REFS:
- TYPE: Parent
  VALUE: AGW-S-008
TITLE: Impervious to Address Claim Attacks
STATEMENT: The device SHALL not be susceptible to address claim attacks on any of its interfaces (e.g. *TND* and *UND*)
PUB_REFS: >>>
https://www.aut.upt.ro/~bgroza/Papers/j1939.pdf and https://doi.org/10.4271/02-14-03-0026 for a description of the address claim attack.

TODO
<<<
CRITICALITY: High

[/SECTION]

[/SECTION]

[SECTION]
TITLE: Security Requirements for Abstract Unintended Gateways

[FREETEXT]
Security requirements that must be satisfied by any device which *could be* a gateway (due to malicious code) but is not intended to be one.
[/FREETEXT]

[REQUIREMENT]
UID: NGW-S-001
TITLE: Security Assurance
STATEMENT: These devices SHALL satisfy a comprehensive set of product security requirements to yield high assurance of correct operation in the face of adversarial inputs to the device.
PUB_REFS: >>>
TODO
<<<
CRITICALITY: High

[SECTION]
TITLE: Prevents Gateway Functions

[REQUIREMENT]
UID: NGW-S-002
REFS:
- TYPE: Parent
  VALUE: NGW-S-001
TITLE: Won't Transport
STATEMENT: These devices SHALL NOT transport/'move' information between two separate network 'domains,' in either bidirection.
PUB_REFS: >>>
TODO
<<<
CRITICALITY: High

[REQUIREMENT]
UID: NGW-S-003
REFS:
- TYPE: Parent
  VALUE: NGW-S-001
TITLE: Won't Translate
STATEMENT: These devices SHALL NOT translate/transform the information between the separate network domains.
PUB_REFS: >>>
TODO
<<<
CRITICALITY: High

[REQUIREMENT]
UID: NGW-S-004
REFS:
- TYPE: Parent
  VALUE: NGW-S-001
TITLE: Won't Filter, Drop or Rate Limit
STATEMENT: These devices SHALL NOT select which information is transported and/or translated between the network domains.
PUB_REFS: >>>
TODO
<<<
CRITICALITY: High

[REQUIREMENT]
UID: NGW-S-005
REFS:
- TYPE: Parent
  VALUE: NGW-S-001
TITLE: Won't Encapsulate
STATEMENT: These devices SHALL NOT encapsulate information as it is transported and/or translated between the network domains.
PUB_REFS: >>>
TODO
<<<
CRITICALITY: High

[/SECTION]

[/SECTION]

[SECTION]
TITLE: Abstract (Intended) Gateway Functional Requirements

[SECTION]
TITLE: Abstract (Intended) Gateway Core Functional Requirements

[FREETEXT]
The following are the functional requirements assumed to be the core of functionality of a vehicle gateway. As is mentioned above, any device which performs one or more of these functions is a gateway device and, furthermore, devices which are not intended to be gateways must have assurances that malicious code will not enable any one of these functionalities.
[/FREETEXT]

[REQUIREMENT]
UID: AGW-F-001
TITLE: Transports
STATEMENT: These devices SHALL transport/'move' information between two separate network 'domains,' **bi-bidirectionally.**

[REQUIREMENT]
UID: AGW-F-002
TITLE: Translates
STATEMENT: These devices SHALL translate/transform the information between the separate network domains but intentions of the data are preserved.

[SECTION]
TITLE: Filters: AGW-F-003* Series

[FREETEXT]
These devices MAY select which information is transported and/or translated between the network domains by satisfying all of these AGW-F-003* requirements:
[/FREETEXT]

[REQUIREMENT]
UID: AGW-F-003a
TITLE: Drops
STATEMENT: These devices MAY select which information is transported based on rules matching content or metadata before (ingress) or after (egress) processing steps in preparation for transport/translate/encapsulate or other forwarding actions.

[REQUIREMENT]
UID: AGW-F-003b
TITLE: Rate Limits
STATEMENT: These devices MAY select which information is transported in a time varying fashion for the purposes of limiting the rate at which the information is put on a network domain.

[/SECTION]

[REQUIREMENT]
UID: AGW-F-004
TITLE: Encapsulates
STATEMENT: These devices MAY encapsulate information as it is transported and/or translated between the network domains.

[/SECTION]

[SECTION]
TITLE: Abstract (Intended) Gateway Additional Functional Requirements

[FREETEXT]
The following are the functional requirements assumed to also be features of intended gateways; however, devices which perform one or more of these functions are not necessarily assumed to be gateway devices -- as was the case with the requirements of the *Abstract (Intended) Gateway Core Functional Requirements* section.
[/FREETEXT]

[REQUIREMENT]
UID: AGW-F-007
TITLE: Controllable
STATEMENT: These devices SHALL be controllable by users with necessary authentication and authorization.

[REQUIREMENT]
UID: AGW-F-008
TITLE: Configurable
STATEMENT: These devices SHALL be configurable by users with necessary authentication and authorization.

[REQUIREMENT]
UID: AGW-F-009
TITLE: Reports
STATEMENT: These devices SHALL report status of operation to users with necessary authentication and authorization.

[REQUIREMENT]
UID: AGW-F-010
TITLE: Diagnoses
STATEMENT: These devices SHALL provide diagnostic commands to users with necessary authentication and authorization.

[/SECTION]

[/SECTION]
